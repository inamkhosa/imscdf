IMSChargingDataTypes {itu-t (0) identified-organization (4) etsi(0) mobileDomain (0) charging (5) imsChargingDataTypes (4) asn1Module (0) version1 (0)}  
DEFINITIONS IMPLICIT TAGS ::=

BEGIN

-- EXPORTS everything

IMPORTS

RecordType, IPAddress, NodeAddress, LocalSequenceNumber, SubscriptionID, TimeStamp, ServiceContextID,ServiceSpecificInfo
FROM GenericChargingDataTypes {itu-t (0) identified-organization (4) etsi(0) mobileDomain (0) charging (5) genericChargingDataTypes (0) asn1Module (0) version1 (0)}  

;
------------------------------------------------------------------------------
--
--  IMS RECORDS
--
------------------------------------------------------------------------------

IMSRecord ::= CHOICE 
--
-- Record values 63-69, 82 are IMS specific
--
{
	sCSCFRecord			[63] SCSCFRecord,
	pCSCFRecord			[64] PCSCFRecord,
	iCSCFRecord			[65] ICSCFRecord,
	mRFCRecord			[66] MRFCRecord,
	mGCFRecord			[67] MGCFRecord,
	bGCFRecord			[68] BGCFRecord,
	aSRecord			[69] ASRecord
	--iBCFRecord			[82] IBCFRecord
	
}



SCSCFRecord 	::= SET
{
	recordType				[0] RecordType,
	retransmission				[1] NULL OPTIONAL,
	sIP-Method				[2] SIP-Method OPTIONAL,
	role-of-Node				[3] Role-of-Node OPTIONAL,
	nodeAddress				[4] NodeAddress OPTIONAL,
	session-Id				[5] Session-Id OPTIONAL,
	list-Of-Calling-Party-Address		[6] ListOfInvolvedParties OPTIONAL,
	called-Party-Address			[7] InvolvedParty OPTIONAL,
	privateUserID				[8] UniversalString OPTIONAL,
	serviceRequestTimeStamp			[9] TimeStamp OPTIONAL,
	serviceDeliveryStartTimeStamp		[10] TimeStamp OPTIONAL,
	serviceDeliveryEndTimeStamp		[11] TimeStamp OPTIONAL,
	recordOpeningTime			[12] TimeStamp OPTIONAL,
	recordClosureTime			[13] TimeStamp OPTIONAL,
	interOperatorIdentifiers		[14] InterOperatorIdentifierlist OPTIONAL,
	localRecordSequenceNumber		[15] LocalSequenceNumber OPTIONAL,
	recordSequenceNumber			[16] INTEGER OPTIONAL,
	causeForRecordClosing			[17] CauseForRecordClosing OPTIONAL,
	incomplete-CDR-Indication		[18] Incomplete-CDR-Indication OPTIONAL,
	iMS-Charging-Identifier		        [19] IMS-Charging-Identifier OPTIONAL,
	list-Of-SDP-Media-Components		[21] SEQUENCE OF Media-Components-List OPTIONAL,
	gGSNaddress				[22] NodeAddress OPTIONAL,
	serviceReasonReturnCode		        [23] UTF8String OPTIONAL,
	list-Of-Message-Bodies			[24] SEQUENCE OF MessageBody OPTIONAL,
	--recordExtensions			[25] ManagementExtensions OPTIONAL, 
	expiresInformation			[26] INTEGER OPTIONAL,
	list-Of-Associated-URI		        [27] ListOfInvolvedParties OPTIONAL,
	event					[28] UTF8String OPTIONAL,
	accessNetworkInformation		[29] OCTET STRING OPTIONAL,
	serviceContextID			[30] ServiceContextID OPTIONAL,
	list-of-subscription-ID			[31] SEQUENCE OF SubscriptionID OPTIONAL,
	list-Of-Early-SDP-Media-Components 	[32] SEQUENCE OF Early-Media-Components-List OPTIONAL,
	iMSCommunicationServiceIdentifier	[33] IMSCommunicationServiceIdentifier OPTIONAL,
	numberPortabilityRouting		[34] NumberPortabilityRouting OPTIONAL,
	carrierSelectRouting			[35] CarrierSelectRouting OPTIONAL,
	applicationServersInformation		[40] SEQUENCE OF ApplicationServersInformation OPTIONAL,
	requested-Party-Address			[41] InvolvedParty OPTIONAL,
	list-Of-Called-Asserted-Identity 	[42] ListOfInvolvedParties OPTIONAL
}

PCSCFRecord 	::= SET
{
	recordType							[0] RecordType,
	retransmission						[1] NULL OPTIONAL,
	sIP-Method							[2] SIP-Method OPTIONAL,
	role-of-Node						[3] Role-of-Node OPTIONAL,
	nodeAddress							[4] NodeAddress OPTIONAL,
	session-Id							[5] Session-Id OPTIONAL,
	list-Of-Calling-Party-Address		[6] ListOfInvolvedParties OPTIONAL,
	called-Party-Address				[7] InvolvedParty OPTIONAL,
	serviceRequestTimeStamp				[9] TimeStamp OPTIONAL,
	serviceDeliveryStartTimeStamp		[10] TimeStamp OPTIONAL,
	serviceDeliveryEndTimeStamp			[11] TimeStamp OPTIONAL,
	recordOpeningTime					[12] TimeStamp OPTIONAL,
	recordClosureTime					[13] TimeStamp OPTIONAL,
	interOperatorIdentifiers			[14] InterOperatorIdentifierlist OPTIONAL,
	localRecordSequenceNumber			[15] LocalSequenceNumber OPTIONAL,
	recordSequenceNumber				[16] INTEGER OPTIONAL,
	causeForRecordClosing				[17] CauseForRecordClosing OPTIONAL,
	incomplete-CDR-Indication			[18] Incomplete-CDR-Indication OPTIONAL,
	iMS-Charging-Identifier				[19] IMS-Charging-Identifier OPTIONAL,
	list-Of-SDP-Media-Components		[21] SEQUENCE OF Media-Components-List OPTIONAL,
	gGSNaddress							[22] NodeAddress OPTIONAL,
	serviceReasonReturnCode				[23] UTF8String OPTIONAL,
	list-Of-Message-Bodies				[24] SEQUENCE OF MessageBody OPTIONAL,
	--recordExtensions					[25] ManagementExtensions OPTIONAL,
	expiresInformation					[26] INTEGER OPTIONAL,
	list-Of-Associated-URI				[27] ListOfInvolvedParties OPTIONAL,
	event								[28] UTF8String OPTIONAL,
	accessNetworkInformation			[29] OCTET STRING OPTIONAL,
	serviceContextID					[30] ServiceContextID OPTIONAL,
	list-of-subscription-ID				[31] SEQUENCE OF SubscriptionID OPTIONAL,
	list-Of-Early-SDP-Media-Components 	[32] SEQUENCE OF Early-Media-Components-List OPTIONAL,
	numberPortabilityRouting			[34] NumberPortabilityRouting OPTIONAL,
	carrierSelectRouting				[35] CarrierSelectRouting OPTIONAL,
	servedPartyIPAddress				[50] ServedPartyIPAddress OPTIONAL
}

ICSCFRecord 	::= SET
{
	recordType						[0] RecordType,
	retransmission					[1] NULL OPTIONAL,
	sIP-Method						[2] SIP-Method OPTIONAL,
	role-of-Node					[3] Role-of-Node OPTIONAL,
	nodeAddress						[4] NodeAddress OPTIONAL,
	session-Id						[5] Session-Id OPTIONAL,
	list-Of-Calling-Party-Address	[6] ListOfInvolvedParties OPTIONAL,
	called-Party-Address			[7] InvolvedParty OPTIONAL,
	serviceRequestTimeStamp			[9] TimeStamp OPTIONAL,
	interOperatorIdentifiers		[14] InterOperatorIdentifierlist OPTIONAL,
	localRecordSequenceNumber		[15] LocalSequenceNumber OPTIONAL,
	causeForRecordClosing			[17] CauseForRecordClosing OPTIONAL,
	incomplete-CDR-Indication		[18] Incomplete-CDR-Indication OPTIONAL,
	iMS-Charging-Identifier			[19] IMS-Charging-Identifier OPTIONAL,
	serviceReasonReturnCode			[23] UTF8String OPTIONAL,
	--recordExtensions				[25] ManagementExtensions OPTIONAL,
	expiresInformation				[26] INTEGER OPTIONAL,
	list-Of-Associated-URI			[27] ListOfInvolvedParties OPTIONAL,
	event							[28] UTF8String OPTIONAL,
	accessNetworkInformation		[29] OCTET STRING OPTIONAL, 
	serviceContextID				[30] ServiceContextID OPTIONAL,
	numberPortabilityRouting		[34] NumberPortabilityRouting OPTIONAL,
	carrierSelectRouting			[35] CarrierSelectRouting OPTIONAL,
	s-CSCF-Information				[61] S-CSCF-Information OPTIONAL
 }

MRFCRecord 	::= SET
{
	recordType							[0] RecordType,
	retransmission						[1] NULL OPTIONAL,
	sIP-Method							[2] SIP-Method OPTIONAL,
	role-of-Node						[3] Role-of-Node OPTIONAL,
	nodeAddress							[4] NodeAddress OPTIONAL,
	session-Id							[5] Session-Id OPTIONAL,
	list-Of-Calling-Party-Address		[6] ListOfInvolvedParties OPTIONAL,
	called-Party-Address				[7] InvolvedParty OPTIONAL,
	serviceRequestTimeStamp				[9] TimeStamp OPTIONAL,
	serviceDeliveryStartTimeStamp		[10] TimeStamp OPTIONAL,
	serviceDeliveryEndTimeStamp			[11] TimeStamp OPTIONAL,
	recordOpeningTime					[12] TimeStamp OPTIONAL,
	recordClosureTime					[13] TimeStamp OPTIONAL,
	interOperatorIdentifiers			[14] InterOperatorIdentifierlist OPTIONAL,
	localRecordSequenceNumber			[15] LocalSequenceNumber OPTIONAL,
	recordSequenceNumber				[16] INTEGER OPTIONAL,
	causeForRecordClosing				[17] CauseForRecordClosing OPTIONAL,
	incomplete-CDR-Indication			[18] Incomplete-CDR-Indication OPTIONAL,
	iMS-Charging-Identifier				[19] IMS-Charging-Identifier OPTIONAL,
	list-Of-SDP-Media-Components		[21] SEQUENCE OF Media-Components-List OPTIONAL,
	gGSNaddress							[22] NodeAddress OPTIONAL,
	serviceReasonReturnCode				[23] UTF8String OPTIONAL,
	--recordExtensions					[25] ManagementExtensions OPTIONAL,
	expiresInformation					[26] INTEGER OPTIONAL,
	event								[28] UTF8String OPTIONAL,
	accessNetworkInformation			[29] OCTET STRING OPTIONAL, 
	serviceContextID					[30] ServiceContextID OPTIONAL,
	list-of-subscription-ID				[31] SEQUENCE OF SubscriptionID OPTIONAL,
	list-Of-Early-SDP-Media-Components 	[32] SEQUENCE OF Early-Media-Components-List OPTIONAL,
	numberPortabilityRouting			[34] NumberPortabilityRouting OPTIONAL,
	carrierSelectRouting				[35] CarrierSelectRouting OPTIONAL,
	applicationServersInformation		[40] SEQUENCE OF ApplicationServersInformation OPTIONAL,
	service-Id							[70] Service-Id OPTIONAL,
	requested-Party-Address				[71] InvolvedParty OPTIONAL,
	list-Of-Called-Asserted-Identity 	[72] ListOfInvolvedParties OPTIONAL
}

MGCFRecord 	::= SET
{
	recordType							[0] RecordType,
	retransmission						[1] NULL OPTIONAL,
	sIP-Method							[2] SIP-Method OPTIONAL,
	role-of-Node						[3] Role-of-Node OPTIONAL,
	nodeAddress							[4] NodeAddress OPTIONAL,
	session-Id							[5] Session-Id OPTIONAL,
	list-Of-Calling-Party-Address		[6] ListOfInvolvedParties OPTIONAL,
	called-Party-Address				[7] InvolvedParty OPTIONAL,
	serviceRequestTimeStamp				[9] TimeStamp OPTIONAL,
	serviceDeliveryStartTimeStamp		[10] TimeStamp OPTIONAL,
	serviceDeliveryEndTimeStamp			[11] TimeStamp OPTIONAL,
	recordOpeningTime					[12] TimeStamp OPTIONAL,
	recordClosureTime					[13] TimeStamp OPTIONAL,
	interOperatorIdentifiers			[14] InterOperatorIdentifierlist OPTIONAL,
	localRecordSequenceNumber			[15] LocalSequenceNumber OPTIONAL,
	recordSequenceNumber				[16] INTEGER OPTIONAL,
	causeForRecordClosing				[17] CauseForRecordClosing OPTIONAL,
	incomplete-CDR-Indication			[18] Incomplete-CDR-Indication OPTIONAL,
	iMS-Charging-Identifier				[19] IMS-Charging-Identifier OPTIONAL,
	list-Of-SDP-Media-Components		[21] SEQUENCE OF Media-Components-List OPTIONAL,
	serviceReasonReturnCode				[23] UTF8String OPTIONAL,
	--recordExtensions					[25] ManagementExtensions OPTIONAL,
	expiresInformation					[26] INTEGER OPTIONAL,
	event								[28] UTF8String OPTIONAL,
	accessNetworkInformation			[29] OCTET STRING OPTIONAL, 
	serviceContextID					[30] ServiceContextID OPTIONAL,
	list-Of-Early-SDP-Media-Components 	[32] SEQUENCE OF Early-Media-Components-List OPTIONAL,
	numberPortabilityRouting			[34] NumberPortabilityRouting OPTIONAL,
	carrierSelectRouting				[35] CarrierSelectRouting OPTIONAL,
	trunkGroupID						[80] TrunkGroupID OPTIONAL,
	bearerService						[81] TransmissionMedium OPTIONAL
}

BGCFRecord 	::= SET
{
	recordType							[0] RecordType,
	retransmission						[1] NULL OPTIONAL,
	sIP-Method							[2] SIP-Method OPTIONAL,
	role-of-Node						[3] Role-of-Node OPTIONAL,
	nodeAddress							[4] NodeAddress OPTIONAL,
	session-Id							[5] Session-Id OPTIONAL,
	list-Of-Calling-Party-Address		[6] ListOfInvolvedParties OPTIONAL,	
	called-Party-Address				[7] InvolvedParty OPTIONAL,
	serviceRequestTimeStamp				[9] TimeStamp OPTIONAL,
	serviceDeliveryStartTimeStamp		[10] TimeStamp OPTIONAL,
	serviceDeliveryEndTimeStamp			[11] TimeStamp OPTIONAL,
	recordOpeningTime					[12] TimeStamp OPTIONAL,
	recordClosureTime					[13] TimeStamp OPTIONAL,
	interOperatorIdentifiers			[14] InterOperatorIdentifierlist OPTIONAL,
	localRecordSequenceNumber			[15] LocalSequenceNumber OPTIONAL,
	recordSequenceNumber				[16] INTEGER OPTIONAL,
	causeForRecordClosing				[17] CauseForRecordClosing OPTIONAL,
	incomplete-CDR-Indication			[18] Incomplete-CDR-Indication OPTIONAL,
	iMS-Charging-Identifier				[19] IMS-Charging-Identifier OPTIONAL,
	list-Of-SDP-Media-Components		[21] SEQUENCE OF Media-Components-List OPTIONAL,
	serviceReasonReturnCode				[23] UTF8String OPTIONAL,
	--recordExtensions					[25] ManagementExtensions OPTIONAL,
	expiresInformation					[26] INTEGER OPTIONAL,
	event								[28] UTF8String OPTIONAL,
	serviceContextID					[30] ServiceContextID OPTIONAL,
	list-Of-Early-SDP-Media-Components 	[32] SEQUENCE OF Early-Media-Components-List OPTIONAL,
	numberPortabilityRouting			[34] NumberPortabilityRouting OPTIONAL,
	carrierSelectRouting				[35] CarrierSelectRouting OPTIONAL
}

ASRecord 	::= SET
{
	recordType							[0] RecordType,
	retransmission						[1] NULL OPTIONAL,
	sIP-Method							[2] SIP-Method OPTIONAL,
	role-of-Node						[3] Role-of-Node OPTIONAL,
	nodeAddress							[4] NodeAddress OPTIONAL,
	session-Id							[5] Session-Id OPTIONAL,
	list-Of-Calling-Party-Address		[6] ListOfInvolvedParties OPTIONAL,	
	called-Party-Address				[7] InvolvedParty OPTIONAL,
	serviceRequestTimeStamp				[9] TimeStamp OPTIONAL,
	serviceDeliveryStartTimeStamp		[10] TimeStamp OPTIONAL,
	serviceDeliveryEndTimeStamp			[11] TimeStamp OPTIONAL,
	recordOpeningTime					[12] TimeStamp OPTIONAL,
	recordClosureTime					[13] TimeStamp OPTIONAL,
	interOperatorIdentifiers			[14] InterOperatorIdentifierlist OPTIONAL,
	localRecordSequenceNumber			[15] LocalSequenceNumber OPTIONAL,
	recordSequenceNumber				[16] INTEGER OPTIONAL,
	causeForRecordClosing				[17] CauseForRecordClosing OPTIONAL,
	incomplete-CDR-Indication			[18] Incomplete-CDR-Indication OPTIONAL,
	iMS-Charging-Identifier				[19] IMS-Charging-Identifier OPTIONAL,
	list-Of-SDP-Media-Components		[21] SEQUENCE OF Media-Components-List OPTIONAL,
	gGSNaddress							[22] NodeAddress OPTIONAL,
	serviceReasonReturnCode				[23] UTF8String OPTIONAL,
	list-Of-Message-Bodies				[24] SEQUENCE OF MessageBody OPTIONAL,
	--recordExtensions					[25] ManagementExtensions OPTIONAL,
	expiresInformation					[26] INTEGER OPTIONAL,
	event								[28] UTF8String OPTIONAL,
	accessNetworkInformation			[29] OCTET STRING OPTIONAL,
	serviceContextID					[30] ServiceContextID OPTIONAL,
	list-of-subscription-ID				[31] SEQUENCE OF SubscriptionID OPTIONAL,
	list-Of-Early-SDP-Media-Components 	[32] SEQUENCE OF Early-Media-Components-List OPTIONAL,
	iMSCommunicationServiceIdentifier	[33] IMSCommunicationServiceIdentifier OPTIONAL,
	numberPortabilityRouting			[34] NumberPortabilityRouting OPTIONAL,
	carrierSelectRouting				[35] CarrierSelectRouting OPTIONAL,
	serviceSpecificInfo					[100] SEQUENCE OF ServiceSpecificInfo OPTIONAL,
	requested-Party-Address				[101] InvolvedParty OPTIONAL,
	list-Of-Called-Asserted-Identity 	[102] ListOfInvolvedParties OPTIONAL,
	alternateChargedPartyAddress		[103] UTF8String  OPTIONAL
}

------------------------------------------------------------------------------
--
--  IMS DATA TYPES
--
------------------------------------------------------------------------------



SIP-Method ::= UniversalString

Session-Id ::= UniversalString

Service-Id ::= UniversalString

ServedPartyIPAddress  ::=  IPAddress 

NumberPortabilityRouting ::= UniversalString

IMS-Charging-Identifier ::= OCTET STRING

S-CSCF-Information ::=  SEQUENCE
{
	mandatoryCapabilities [0] SEQUENCE OF UniversalString OPTIONAL,
	optionalCapabilities  [1] SEQUENCE OF UniversalString OPTIONAL,
	serverName 	      [2] UniversalString OPTIONAL
}


Role-of-Node ::= ENUMERATED 
{
	originating (0),
	terminating (1),
	proxy       (2),
	b2bua       (3)
}

AccessCorrelationID ::= CHOICE 
{
	gPRS-Charging-Id[2] INTEGER , -- removed OPTIONAL form here as it is giving error
	accessNetworkChargingIdentifier[4] UniversalString  -- removed OPTIONAL form here as it is giving error
} 

InvolvedParty ::= CHOICE 
{
	sIP-URI[0] UniversalString, -- refer to rfc3261
	tEL-URI[1] UniversalString  -- refer to rfc3966
}

--Editor’s note:  the constructs below are imported from the generic module

ListOfInvolvedParties ::= SEQUENCE OF InvolvedParty

InterOperatorIdentifierlist ::= SEQUENCE OF InterOperatorIdentifiers

InterOperatorIdentifiers ::= SEQUENCE 
{ 
	originatingIOI[0] UniversalString OPTIONAL,
	terminatingIOI[1] UniversalString OPTIONAL
}

CauseForRecordClosing ::= ENUMERATED 
{
	serviceDeliveryEndSuccessfully	(0),
	unSuccessfulServiceDelivery	(1),
	timeLimit			(3),
	serviceChange			(4), -- e.g. change in media due to Re-Invite
	managementIntervention		(5)  -- partial record generation reasons to be added
					     --  Additional codes are for further study
}



ACRInterimLost ::= ENUMERATED 
{
	no 	(0),
	yes 	(1),
	unknown (2)
}

Incomplete-CDR-Indication ::= SET 
{
	aCRStartLost	[0] BOOLEAN, -- TRUE if ACR[Start] was lost, FALSE otherwise
	aCRInterimLost	[1] ACRInterimLost, 
	aCRStopLost	[2] BOOLEAN -- TRUE if ACR[Stop] was lost, FALSE otherwise
} 

ApplicationServersInformation ::= SEQUENCE 
{	applicationServersInvolved 			[0] NodeAddress OPTIONAL,
	applicationProvidedCalledParties	[1] SEQUENCE OF InvolvedParty OPTIONAL
}

CarrierSelectRouting ::= UniversalString

SDP-Media-Description ::= SEQUENCE OF UniversalString



SDP-Media-Component ::=  SEQUENCE
{
	sDP-Media-Name        	[0] UniversalString OPTIONAL,
	sDP-Media-Descriptions	[1] SDP-Media-Description OPTIONAL,
	accessCorrelationID	AccessCorrelationID OPTIONAL, 	
	authorized-QoS        	[3] UniversalString OPTIONAL    
}

Media-Components-List ::= SEQUENCE 
{
	sIP-Request-Timestamp 	[0] TimeStamp OPTIONAL,
	sIP-Response-Timestamp	[1] TimeStamp OPTIONAL,
	sDP-Media-Components	[2] SEQUENCE OF SDP-Media-Component OPTIONAL,
	mediaInitiatorFlag		[3] NULL OPTIONAL,
	sDP-Session-Description	[4] SEQUENCE OF UniversalString OPTIONAL,
	mediaInitiatorParty		[5] InvolvedParty OPTIONAL

--- MediaInitiatorParty is used to identify the initiator of the media 
--- multi-participants session e.g. in AS PoC Server
}

Early-Media-Components-List ::= SEQUENCE 
{
	sDP-Offer-Timestamp 	[0] TimeStamp OPTIONAL,
	sDP-Answer-Timestamp	[1] TimeStamp OPTIONAL,
	sDP-Media-Components	[2] SEQUENCE OF SDP-Media-Component OPTIONAL,
	mediaInitiatorFlag	[3] NULL OPTIONAL,
	sDP-Session-Description	[4] SEQUENCE OF UniversalString OPTIONAL
}

IMSCommunicationServiceIdentifier	::= OCTET STRING

MessageBody ::= SEQUENCE 
{
	content-Type			[0] UniversalString,
	content-Disposition		[1] UniversalString OPTIONAL,
	content-Length			[2] INTEGER,
	originator			[3] InvolvedParty OPTIONAL
}

TransmissionMedium ::= SEQUENCE 
{
	tMR	[0] OCTET STRING (SIZE (1)) OPTIONAL, -- required TM, refer to ITU-T Q.763
	tMU	[1] OCTET STRING (SIZE (1)) OPTIONAL  -- used TM, refer to ITU-T Q.763
}

TrunkGroupID ::= CHOICE 
{
	incoming	[0] UniversalString,
	outgoing	[1] UniversalString
}


END
